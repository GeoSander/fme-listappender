FME workspace ListAppenderTest.fmw

Creator
    NUM = 3
    GEOMTYPE = Geometry Object
    CREATED -> ListBuilder
    CREATED -> ListBuilder_2
ListBuilder
    LIST_ATTRS_TO_INCLUDE = value
    LIST_NAME = parent
    -> ListAppender
    -> ListAppender_2
    -> ListAppender_3
    -> ListAppender_5
Note: append to unicode_test / (SHOULD FAIL!)
ListAppender_5
    APPEND_VALUES = @Evaluate(12.345) @Value(unicode_test) new string  @Value(parent{0}.value) FME_NULL_VALUE Zürich 2
    APPEND_LIST = unicode_test
    APPEND_VALUES_WWJD = return FME_MacroValues['APPEND_VALUES']
    -> Output_5
    <Rejected> -> Rejected_5
Output_5: Logger
    MESSAGE = Feature is:
    MAXFEATS = 20
    MAXCOORDS = 20
    LOGGED -> Terminator_5
Terminator_5
    MESSAGE = Selecting a non-list attribute should fail
Rejected_5: Logger
    MESSAGE = Feature is:
    MAXFEATS = 20
    MAXCOORDS = 20
Note: append to parent{}.value
ListAppender
    APPEND_VALUES = @Evaluate(12.345) @Value(unicode_test) new string  @Value(parent{0}.value) FME_NULL_VALUE Zürich 2
    APPEND_LIST = parent{0}.value
    APPEND_VALUES_WWJD = return FME_MacroValues['APPEND_VALUES']
    -> Output
    <Rejected> -> Rejected
Note: Output should be: / Attribute(32 bit unsigned integer): `parent{0}.value' has value `0' / Attribute(32 bit unsigned integer): `parent{1}.value' has value `1' / Attribute(32 bit unsigned integer): `parent{2}.value' has value `2' / Attribute(encoded: utf-8) : `parent{3}.value' has value `existing string' / Attribute(64 bit real) : `parent{4}.value' has value `12.345' / Attribute(encoded: utf-8) : `parent{5}.value' has value `Zürich' / Attribute(encoded: utf-8) : `parent{6}.value' has value `new string' / Attribute(encoded: utf-8) : `parent{7}.value' has value `' / Attribute(32 bit integer) : `parent{8}.value' has value `0' / Attribute(string) : `parent{9}.value' is <null> / Attribute(encoded: utf-8) : `parent{10}.value' has value `Zürich 2'
Output: Logger
    MESSAGE = Feature is:
    MAXFEATS = 20
    MAXCOORDS = 20
    LOGGED -> Tester
Tester
    BOOL_OP = AND
    TEST_DESCRIPTION = ""
    TEST_MODE = Automatic
    TEST_CLAUSE:
      NUM_TEST @Value(parent{4}.value) TYPE DOUBLE
      TEST @Value(parent{5}.value) = Zürich
      STRING_TEST @Value(parent{7}.value) = ""
      NUM_TEST @Value(parent{8}.value) TYPE INT
      TEST parent{9}.value ATTRIBUTE_VALUE_NULL ""
      TEST @Value(parent{10}.value) ATTRIBUTE_HAS_VALUE ""
    FAILED -> Terminator_6
Note: Python 3.4+
Note: Output should be: / Attribute(32 bit unsigned integer): `parent{0}.value' has value `0' / Attribute(32 bit unsigned integer): `parent{1}.value' has value `1' / Attribute(32 bit unsigned integer): `parent{2}.value' has value `2' / Attribute(encoded: utf-8) : `parent{3}.value' has value `existing string' / Attribute(64 bit real) : `parent{4}.value' has value `12.345' / Attribute(encoded: utf-8) : `parent{5}.value' has value `Zürich' / Attribute(string) : `parent{6}.value' has value `new string' / Attribute(string) : `parent{7}.value' has value `' / Attribute(32 bit integer) : `parent{8}.value' has value `0' / Attribute(string) : `parent{9}.value' is <null> / Attribute(encoded: utf-8) : `parent{10}.value' has value `Zürich 2'
Note: Output should be: / Attribute(32 bit unsigned integer): `parent{0}.value' has value `0' / Attribute(32 bit unsigned integer): `parent{1}.value' has value `1' / Attribute(32 bit unsigned integer): `parent{2}.value' has value `2' / Attribute(encoded: utf-8) : `parent{3}.value' has value `existing string' / Attribute(64 bit real) : `parent{10}.value' has value `12.345' / Attribute(encoded: utf-8) : `parent{11}.value' has value `Zürich' / Attribute(string) : `parent{12}.value' has value `new string' / Attribute(string) : `parent{13}.value' has value `' / Attribute(32 bit integer) : `parent{14}.value' has value `0' / Attribute(string) : `parent{15}.value' is <null> / Attribute(encoded: utf-8) : `parent{16}.value' has value `Zürich 2'
Note: Python 2.7
Terminator_6
    MESSAGE = Output value checks failed
Rejected: Logger
    MESSAGE = Feature is:
    MAXFEATS = 20
    MAXCOORDS = 20
    LOGGED -> Terminator
Terminator
    MESSAGE = Action should not fail
Note: append starting from parent{10}.value
ListAppender_2
    APPEND_VALUES = @Evaluate(12.345) @Value(unicode_test) new string  @Value(parent{0}.value) FME_NULL_VALUE Zürich 2
    APPEND_LIST = parent{10}.value
    APPEND_VALUES_WWJD = return FME_MacroValues['APPEND_VALUES']
    -> Output_2
    <Rejected> -> Rejected_2
Note: Output should be: / Attribute(32 bit unsigned integer): `parent{0}.value' has value `0' / Attribute(32 bit unsigned integer): `parent{1}.value' has value `1' / Attribute(32 bit unsigned integer): `parent{2}.value' has value `2' / Attribute(encoded: utf-8) : `parent{3}.value' has value `existing string' / Attribute(64 bit real) : `parent{10}.value' has value `12.345' / Attribute(encoded: utf-8) : `parent{11}.value' has value `Zürich' / Attribute(encoded: utf-8) : `parent{12}.value' has value `new string' / Attribute(encoded: utf-8) : `parent{13}.value' has value `' / Attribute(32 bit integer) : `parent{14}.value' has value `0' / Attribute(string) : `parent{15}.value' is <null> / Attribute(encoded: utf-8) : `parent{16}.value' has value `Zürich 2'
Output_2: Logger
    MESSAGE = Feature is:
    MAXFEATS = 20
    MAXCOORDS = 20
Rejected_2: Logger
    MESSAGE = Feature is:
    MAXFEATS = 20
    MAXCOORDS = 20
    LOGGED -> Terminator_2
Terminator_2
    MESSAGE = Action should not fail
Note: append to parent{}
ListAppender_3
    APPEND_VALUES = @Evaluate(12.345) @Value(unicode_test) new string  @Value(parent{0}) FME_NULL_VALUE Zürich 2
    APPEND_LIST = parent{0}
    APPEND_VALUES_WWJD = return FME_MacroValues['APPEND_VALUES']
    -> Output_3
    <Rejected> -> Rejected_3
Note: Output should be: / Attribute(encoded: utf-8) : `parent{0}' has value `root element' / Attribute(64 bit real) : `parent{1}' has value `12.345' / Attribute(encoded: utf-8) : `parent{2}' has value `Zürich' / Attribute(encoded: utf-8) : `parent{3}' has value `new string' / Attribute(encoded: utf-8) : `parent{4}' has value `' / Attribute(encoded: utf-8) : `parent{5}' has value `root element' / Attribute(string) : `parent{6}' is <null> / Attribute(encoded: utf-8) : `parent{7}' has value `Zürich 2'
Output_3: Logger
    MESSAGE = Feature is:
    MAXFEATS = 20
    MAXCOORDS = 20
Rejected_3: Logger
    MESSAGE = Feature is:
    MAXFEATS = 20
    MAXCOORDS = 20
    LOGGED -> Terminator_3
Terminator_3
    MESSAGE = Action should not fail
ListBuilder_2
    LIST_ATTRS_TO_INCLUDE = value
    LIST_NAME = child
    -> Cloner
Cloner
    COPIES = 3
    COPY -> ListBuilder_3
ListBuilder_3
    LIST_ATTRS_TO_INCLUDE = child{}.value
    LIST_NAME = _parent
    -> ListAppender_4
Note: append to child elements of parent{1} / (nested list scenario)
ListAppender_4
    APPEND_VALUES = @Evaluate(12.345) new string FME_NULL_VALUE Zürich
    APPEND_LIST = _parent{1}.child{0}.value
    APPEND_VALUES_WWJD = return FME_MacroValues['APPEND_VALUES']
    -> Output_4
    <Rejected> -> Rejected_4
Note: Output should be: / Attribute(32 bit unsigned integer): `_parent{0}.child{0}.value' has value `0' / Attribute(32 bit unsigned integer): `_parent{0}.child{1}.value' has value `1' / Attribute(32 bit unsigned integer): `_parent{0}.child{2}.value' has value `2' / Attribute(32 bit unsigned integer): `_parent{1}.child{0}.value' has value `0' / Attribute(32 bit unsigned integer): `_parent{1}.child{1}.value' has value `1' / Attribute(32 bit unsigned integer): `_parent{1}.child{2}.value' has value `2' / Attribute(64 bit real) : `_parent{1}.child{3}.value' has value `12.345' / Attribute(encoded: utf-8) : `_parent{1}.child{4}.value' has value `new string' / Attribute(string) : `_parent{1}.child{5}.value' is <null> / Attribute(encoded: utf-8) : `_parent{1}.child{6}.value' has value `Zürich' / Attribute(32 bit unsigned integer): `_parent{2}.child{0}.value' has value `0' / Attribute(32 bit unsigned integer): `_parent{2}.child{1}.value' has value `1' / Attribute(32 bit unsigned integer): `_parent{2}.child{2}.value' has value `2'
Output_4: Logger
    MESSAGE = Feature is:
    MAXFEATS = 20
    MAXCOORDS = 20
Rejected_4: Logger
    MESSAGE = Feature is:
    MAXFEATS = 20
    MAXCOORDS = 20
    LOGGED -> Terminator_4
Note: Output should be: / Attribute(encoded: utf-8) : `parent{0}' has value `root element' / Attribute(64 bit real) : `parent{1}' has value `12.345' / Attribute(encoded: utf-8) : `parent{2}' has value `Zürich' / Attribute(string) : `parent{3}' has value `new string' / Attribute(string) : `parent{4}' has value `' / Attribute(string) : `parent{5}' has value `root element' / Attribute(string) : `parent{6}' is <null> / Attribute(encoded: utf-8) : `parent{7}' has value `Zürich 2'
Note: Output should be: / Attribute(32 bit unsigned integer): `_parent{0}.child{0}.value' has value `0' / Attribute(32 bit unsigned integer): `_parent{0}.child{1}.value' has value `1' / Attribute(32 bit unsigned integer): `_parent{0}.child{2}.value' has value `2' / Attribute(32 bit unsigned integer): `_parent{1}.child{0}.value' has value `0' / Attribute(32 bit unsigned integer): `_parent{1}.child{1}.value' has value `1' / Attribute(32 bit unsigned integer): `_parent{1}.child{2}.value' has value `2' / Attribute(64 bit real) : `_parent{1}.child{3}.value' has value `12.345' / Attribute(string) : `_parent{1}.child{4}.value' has value `new string' / Attribute(string) : `_parent{1}.child{5}.value' is <null> / Attribute(encoded: utf-8) : `_parent{1}.child{6}.value' has value `Zürich' / Attribute(32 bit unsigned integer): `_parent{2}.child{0}.value' has value `0' / Attribute(32 bit unsigned integer): `_parent{2}.child{1}.value' has value `1' / Attribute(32 bit unsigned integer): `_parent{2}.child{2}.value' has value `2'
Terminator_4
    MESSAGE = Action should not fail
